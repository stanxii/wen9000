NSCRTV-HFCEMS-FIBERNODE-MIB DEFINITIONS ::= BEGIN

IMPORTS
    OBJECT-TYPE
        FROM RFC-1212
    DisplayString
        FROM RFC1213-MIB
    fnIdent
        FROM NSCRTV-ROOT;

    fnVendorOID OBJECT-TYPE
        SYNTAX OBJECT IDENTIFIER
        ACCESS read-only
        STATUS optional
        DESCRIPTION
            ""
        ::= { fnIdent 1 }


 
    fnNumberReturnLaser OBJECT-TYPE
        SYNTAX INTEGER ( 0..16 )
        ACCESS read-write
        STATUS mandatory
        DESCRIPTION
            ""
        ::= { fnIdent 2 }
    
    fnReturnLaserTable OBJECT-TYPE
        SYNTAX SEQUENCE OF FnReturnLaserEntry
        ACCESS not-accessible
        STATUS mandatory
        DESCRIPTION
            ""
        ::= { fnIdent 3 }
    
    fnReturnLaserEntry OBJECT-TYPE
        SYNTAX FnReturnLaserEntry ACCESS not-accessible
        STATUS mandatory
        DESCRIPTION
            ""
        INDEX { fnReturnLaserIndex }
        ::= { fnReturnLaserTable 1 }
    
    FnReturnLaserEntry ::= SEQUENCE
    {
        fnReturnLaserIndex
            INTEGER,
        fnReturnLaserCurrent
            INTEGER,
        fnReturnLaserTemp
            INTEGER,
        fnReturnLaserControl
            INTEGER,
        fnReturnLaserType
            DisplayString,
        fnReturnLaserWavelength
            DisplayString,
        fnReturnLaserOpticalPower
            INTEGER,
        fnReturnLaserRFActive
            INTEGER
    }
    
    fnReturnLaserIndex OBJECT-TYPE
        SYNTAX INTEGER
        ACCESS read-only
        STATUS mandatory
        DESCRIPTION
            ""
        ::= { fnReturnLaserEntry 1 }
    
    fnReturnLaserCurrent OBJECT-TYPE
        SYNTAX INTEGER ( 0..65535 )
        ACCESS read-only
        STATUS optional
        DESCRIPTION
            ""
        ::= { fnReturnLaserEntry 2 }
    
    fnReturnLaserTemp OBJECT-TYPE
        SYNTAX INTEGER ( -32768..32767 )
        ACCESS read-only
        STATUS optional
        DESCRIPTION
            ""
        ::= { fnReturnLaserEntry 3 }
    
    fnReturnLaserControl OBJECT-TYPE
        SYNTAX INTEGER { off(1), on(2) }
        ACCESS read-write
        STATUS optional
        DESCRIPTION
            ""
        ::= { fnReturnLaserEntry 4 }
    
    fnReturnLaserType OBJECT-TYPE
        SYNTAX DisplayString
        ACCESS read-only
        STATUS optional
        DESCRIPTION
            ""
        ::= { fnReturnLaserEntry 5 }
    
    fnReturnLaserWavelength OBJECT-TYPE
        SYNTAX DisplayString
        ACCESS read-only
        STATUS optional
        DESCRIPTION
            ""
        ::= { fnReturnLaserEntry 6 }
    
    fnReturnLaserOpticalPower OBJECT-TYPE
        SYNTAX INTEGER ( 0..65535 )
        ACCESS read-only
        STATUS mandatory
        DESCRIPTION
            ""
        ::= { fnReturnLaserEntry 7 }
    
    fnReturnLaserRFActive OBJECT-TYPE
        SYNTAX INTEGER
        ACCESS read-only
        STATUS mandatory
        DESCRIPTION
            ""
        ::= { fnReturnLaserEntry 8 }



    fnNumberOpticalReceiver OBJECT-TYPE
        SYNTAX INTEGER ( 0..16 )
        ACCESS read-only
        STATUS mandatory
        DESCRIPTION
            ""
        ::= { fnIdent 4 }
    
    fnOpticalReceiverTable OBJECT-TYPE
        SYNTAX SEQUENCE OF FnOpticalReceiverEntry
        ACCESS not-accessible
        STATUS mandatory
        DESCRIPTION
            ""
        ::= { fnIdent 5}
    
    fnOpticalReceiverEntry OBJECT-TYPE
        SYNTAX FnOpticalReceiverEntry
        ACCESS not-accessible
        STATUS mandatory
        DESCRIPTION
            ""
            INDEX { fnOpticalReceiverIndex }
        ::= { fnOpticalReceiverTable 1 }
    
    FnOpticalReceiverEntry ::= SEQUENCE
        {
        fnOpticalReceiverIndex
            INTEGER,
        fnOpticalReceiverPower
            INTEGER,
        fnOpticalReceiverState
            INTEGER,
        fnOpticalReceiverRFActive
            INTEGER
        }
    
    fnOpticalReceiverIndex OBJECT-TYPE
        SYNTAX INTEGER
        ACCESS read-only
        STATUS mandatory
        DESCRIPTION
            ""
        ::= { fnOpticalReceiverEntry 1 }
    
    fnOpticalReceiverPower OBJECT-TYPE
        SYNTAX INTEGER ( 0..65535 )
        ACCESS read-only
        STATUS mandatory
        DESCRIPTION
            ""
        ::= { fnOpticalReceiverEntry 2 }
    
    fnOpticalReceiverState OBJECT-TYPE
        SYNTAX INTEGER { off(1), on(2) }
        ACCESS read-only
        STATUS optional
        DESCRIPTION
            ""
        ::= { fnOpticalReceiverEntry 3 }
    
    fnOpticalReceiverRFActive OBJECT-TYPE
        SYNTAX INTEGER
        ACCESS read-only
        STATUS mandatory
        DESCRIPTION
            ""
        ::= { fnOpticalReceiverEntry 4 }


    fnOpticalAmpPresent OBJECT-TYPE
        SYNTAX INTEGER { no(1), yes(2) }
        ACCESS read-only
        STATUS mandatory
        DESCRIPTION
            ""
        ::= { fnIdent 6 }


  
    fnNumberRFActives OBJECT-TYPE
        SYNTAX INTEGER ( 1..16 )
        ACCESS read-only
        STATUS mandatory
        DESCRIPTION
            ""
        ::= { fnIdent 7}
    
    fnRFActiveTable OBJECT-TYPE
        SYNTAX SEQUENCE OF FnRFActiveEntry
        ACCESS not-accessible
        STATUS mandatory
        DESCRIPTION
            ""
        ::= { fnIdent 8}
    
    fnRFActiveEntry OBJECT-TYPE
        SYNTAX FnRFActiveEntry
        ACCESS not-accessible
        STATUS mandatory
        DESCRIPTION
            ""
        INDEX { fnRFActiveIndex }
        ::= { fnRFActiveTable 1 }
    
    FnRFActiveEntry ::= SEQUENCE
        {
        fnRFActiveIndex
            INTEGER,
        fnRFActiveControlType
            INTEGER,
        fnRFActiveOutputLevel
            INTEGER,
        fnRFActiveCurrent
            INTEGER,
        fnRFActiveControlLevel
            INTEGER
        }
    
    fnRFActiveIndex OBJECT-TYPE
        SYNTAX INTEGER
        ACCESS read-only
        STATUS mandatory
        DESCRIPTION
            ""
        ::= { fnRFActiveEntry 1 }
    
    fnRFActiveControlType OBJECT-TYPE
        SYNTAX INTEGER { alc(1), asc(2), agc(3), none(4) }
        ACCESS read-only
        STATUS optional
        DESCRIPTION
            ""
        ::= { fnRFActiveEntry 2 }
    
    fnRFActiveOutputLevel OBJECT-TYPE
        SYNTAX INTEGER ( 0..127 )
        ACCESS read-only
        STATUS optional
        DESCRIPTION
            ""
        ::= { fnRFActiveEntry 3 }
    
    fnRFActiveCurrent OBJECT-TYPE
        SYNTAX INTEGER ( 0..65535 )
        ACCESS read-only
        STATUS optional
        DESCRIPTION
            ""
        ::= { fnRFActiveEntry 4 }
    
    fnRFActiveControlLevel OBJECT-TYPE
        SYNTAX INTEGER
        ACCESS read-only
        STATUS optional
        DESCRIPTION
            ""
        ::= { fnRFActiveEntry 5 }


  
    fnNumberRFPort OBJECT-TYPE
        SYNTAX INTEGER ( 0..16 )
        ACCESS read-only
        STATUS mandatory
        DESCRIPTION
            ""
        ::= { fnIdent 9 }
    
    fnPortMasterAttenuationControl OBJECT-TYPE
        SYNTAX INTEGER { none(1), low(2), high(3) }
        ACCESS read-write
        STATUS optional
        DESCRIPTION
            ""
        ::= { fnIdent 10 }
    
    fnRFPortTable OBJECT-TYPE
        SYNTAX SEQUENCE OF FnRFPortEntry
        ACCESS not-accessible
        STATUS mandatory
        DESCRIPTION
            ""
        ::= { fnIdent 11 }
    
    fnRFPortEntry OBJECT-TYPE
        SYNTAX FnRFPortEntry
        ACCESS not-accessible
        STATUS mandatory
        DESCRIPTION
            ""
        INDEX { fnRFPortIndex }
        ::= { fnRFPortTable 1 }
    
    FnRFPortEntry ::= SEQUENCE
        {
        fnRFPortIndex
            INTEGER,
        fnRFPortControlType
            INTEGER,
        fnRFPortControlLevel
            INTEGER,
        fnRFPortOutputRFLevel
            INTEGER,
        fnRFPortRFActive
            INTEGER,
        fnRFPortName
            DisplayString,
        fnRFPortReverseAttenuationControl
            INTEGER,
        fnRFPortPowerFeedStatus
            INTEGER,
        fnRFPortRFlevelatt 
            INTEGER,
        fnRFPortRFleveleq  
            INTEGER,
        fnRFPortReverseatt 
            INTEGER,
        fnRFPortReverseeq
            INTEGER

        }
    
    fnRFPortIndex OBJECT-TYPE
        SYNTAX INTEGER
        ACCESS read-only
        STATUS mandatory
        DESCRIPTION
            ""
        ::= { fnRFPortEntry 1 }
    
    fnRFPortControlType OBJECT-TYPE
        SYNTAX INTEGER { alc(1), asc(2), agc(3), none(4) }
        ACCESS read-only
        STATUS optional
        DESCRIPTION
            ""
        ::= { fnRFPortEntry 2 }
    
    fnRFPortControlLevel OBJECT-TYPE
        SYNTAX INTEGER
        ACCESS read-only
        STATUS optional
        DESCRIPTION
            ""
        ::= { fnRFPortEntry 3 }
    
    fnRFPortOutputRFLevel OBJECT-TYPE
        SYNTAX INTEGER ( 0..127 )
        ACCESS read-only
        STATUS optional
        DESCRIPTION
            ""
        ::= { fnRFPortEntry 4 }
    
    fnRFPortRFActive OBJECT-TYPE
        SYNTAX INTEGER
        ACCESS read-only
        STATUS mandatory
        DESCRIPTION
            ""
        ::= { fnRFPortEntry 5 }
    
    fnRFPortName OBJECT-TYPE
        SYNTAX DisplayString
        ACCESS read-only
        STATUS mandatory
        DESCRIPTION
            ""
        ::= { fnRFPortEntry 6 }
    
    fnRFPortReverseAttenuationControl OBJECT-TYPE
        SYNTAX INTEGER { none(1), low(2), high(3) }
        ACCESS read-write
        STATUS optional
        DESCRIPTION
            ""
        ::= { fnRFPortEntry 7 }
    
    fnRFPortPowerFeedStatus OBJECT-TYPE
        SYNTAX INTEGER { on(1),off(2) }
        ACCESS read-only
        STATUS optional
        DESCRIPTION
            ""
        ::= { fnRFPortEntry 8 }
    fnRFPortRFlevelatt OBJECT-TYPE
        SYNTAX INTEGER ( 0..65535 )
        ACCESS read-write
        STATUS optional
        DESCRIPTION
            ""
        ::= { fnRFPortEntry 9 }

      fnRFPortRFleveleq OBJECT-TYPE
        SYNTAX INTEGER ( 0..65535 )
        ACCESS read-write
        STATUS optional
        DESCRIPTION
            ""
        ::= { fnRFPortEntry 10 }

       fnRFPortReverseatt OBJECT-TYPE
        SYNTAX INTEGER ( 0..65535 )
        ACCESS read-write
        STATUS optional
        DESCRIPTION
            ""
        ::= { fnRFPortEntry 11 }

       fnRFPortReverseeq OBJECT-TYPE
        SYNTAX INTEGER ( 0..65535 )
        ACCESS read-write
        STATUS optional
        DESCRIPTION
            ""
        ::= { fnRFPortEntry 12 }


    fnNumberABSwitch OBJECT-TYPE
        SYNTAX INTEGER ( 0..16)
        ACCESS read-only
        STATUS mandatory
        DESCRIPTION
            ""
        ::= { fnIdent 12 }
    
    fnABSwitchTable OBJECT-TYPE
        SYNTAX SEQUENCE OF FnABSwitchEntry
        ACCESS not-accessible
        STATUS mandatory
        DESCRIPTION
            ""
        ::= { fnIdent 13 }
    
    fnABSwitchEntry OBJECT-TYPE
        SYNTAX FnABSwitchEntry
        ACCESS not-accessible
        STATUS mandatory
        DESCRIPTION
            ""
        INDEX { fnABSwitchIndex }
        ::= { fnABSwitchTable 1 }
    
    FnABSwitchEntry ::= SEQUENCE
        {
        fnABSwitchIndex
            INTEGER,
        fnOpticalReceiverABSwitchState
            INTEGER,
        fnOpticalReceiverABSwitchControl
            INTEGER
        }
    
    fnABSwitchIndex OBJECT-TYPE
        SYNTAX INTEGER
        ACCESS read-only
        STATUS mandatory
        DESCRIPTION
            ""
        ::= { fnABSwitchEntry 1 }
    
    fnOpticalReceiverABSwitchState OBJECT-TYPE
        SYNTAX INTEGER { pathA(1), pathB(2) }
        ACCESS read-only
        STATUS mandatory
        DESCRIPTION
            ""
        ::= { fnABSwitchEntry 2 }
    
    fnOpticalReceiverABSwitchControl OBJECT-TYPE
        SYNTAX INTEGER { forcePathA(1), forcePathB(2), preferPathA(3), preferPathB(4) }
        ACCESS read-write
        STATUS mandatory
        DESCRIPTION
            ""
        ::= { fnABSwitchEntry 3 }


 
    fnLinePowerVoltage1 OBJECT-TYPE
        SYNTAX INTEGER ( 0..65535 )
        ACCESS read-only
        STATUS optional
        DESCRIPTION
            ""
        ::= { fnIdent 14 }
    
    fnLinePowerVoltage2 OBJECT-TYPE
        SYNTAX INTEGER ( 0..65535 )
        ACCESS read-only
        STATUS optional
        DESCRIPTION
            ""
        ::= { fnIdent 15 }
    
    fnLinePowerCurrent OBJECT-TYPE
        SYNTAX INTEGER ( 0..65535 )
        ACCESS read-only
        STATUS optional
        DESCRIPTION
            ""
        ::= { fnIdent 16}


 
    fnNumberDCPowerSupply OBJECT-TYPE
        SYNTAX INTEGER ( 0..16 )
        ACCESS read-only
        STATUS mandatory
        DESCRIPTION
            ""
        ::= { fnIdent 17 }
    
    fnDCPowerSupplyMode OBJECT-TYPE
        SYNTAX INTEGER { loadsharing(1), switchedRedundant(2) }
        ACCESS read-only
        STATUS optional
        DESCRIPTION
            ""
        ::= { fnIdent 18 }
    
    fnDCPowerTable OBJECT-TYPE
        SYNTAX SEQUENCE OF FnDCPowerEntry
        ACCESS not-accessible
        STATUS mandatory
        DESCRIPTION
            ""
        ::= { fnIdent 19 }
    
    fnDCPowerEntry OBJECT-TYPE
        SYNTAX FnDCPowerEntry
        ACCESS not-accessible
        STATUS mandatory
        DESCRIPTION
            ""
        INDEX { fnDCPowerIndex }
        ::= { fnDCPowerTable 1 }
    
    FnDCPowerEntry ::= SEQUENCE
        {
        fnDCPowerIndex
            INTEGER,
        fnDCPowerVoltage
            INTEGER,
        fnDCPowerCurrent
            INTEGER,
        fnDCPowerName
            DisplayString
        }
    
    fnDCPowerIndex OBJECT-TYPE
        SYNTAX INTEGER
        ACCESS read-only
        STATUS mandatory
        DESCRIPTION
            ""
        ::= { fnDCPowerEntry 1 }
    
    fnDCPowerVoltage OBJECT-TYPE
        SYNTAX INTEGER ( -32768..32767 )
        ACCESS read-only
        STATUS mandatory
        DESCRIPTION
            ""
        ::= { fnDCPowerEntry 2 }
    
    fnDCPowerCurrent OBJECT-TYPE
        SYNTAX INTEGER ( 0..65535 )
        ACCESS read-only
        STATUS optional
        DESCRIPTION
            ""
        ::= { fnDCPowerEntry 3 }
    
    fnDCPowerName OBJECT-TYPE
        SYNTAX DisplayString
        ACCESS read-only
        STATUS mandatory
        DESCRIPTION
            ""
        ::= { fnDCPowerEntry 4 }


 fnReturnRFPower OBJECT-TYPE
        SYNTAX INTEGER (0..65536)
        ACCESS read-write
        STATUS mandatory
        DESCRIPTION
            ""
        ::= { fnIdent 26 }


END
