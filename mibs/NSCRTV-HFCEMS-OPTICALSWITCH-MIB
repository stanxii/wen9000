NSCRTV-HFCEMS-OPTICALSWITCH-MIB DEFINITIONS ::= BEGIN

-- *****************************************************************************
--                             杭州万隆光开关MIB
-- *****************************************************************************

IMPORTS
    OBJECT-TYPE
        FROM RFC-1212
    DisplayString
        FROM RFC1213-MIB
    nscrtvHFCemsTree
        FROM NSCRTV-ROOT
    commonPhysAddress
        FROM NSCRTV-HFCEMS-COMMON-MIB
    commonNELogicalID
        FROM NSCRTV-HFCEMS-COMMON-MIB;
    
osIdent OBJECT IDENTIFIER ::= { nscrtvHFCemsTree 8686 }
    
    osVendorOID OBJECT-TYPE
        SYNTAX OBJECT IDENTIFIER
        ACCESS read-only
        STATUS optional
        DESCRIPTION
            ""
        ::= { osIdent 1 }
        
    osWavelength OBJECT-TYPE
        SYNTAX INTEGER {1310nm(1),1490nm(2),1550nm(3)}
        ACCESS read-write
        STATUS mandatory
        DESCRIPTION
            ""
        ::= { osIdent 2 }
    
    osAutoControl OBJECT-TYPE
        SYNTAX INTEGER {off(1),on(2)}
        ACCESS read-write
        STATUS mandatory
        DESCRIPTION
            ""
        ::= { osIdent 3 }
    
    osCurrentWorkChannel OBJECT-TYPE
        SYNTAX INTEGER {A(1),B(2)}
        ACCESS read-write
        STATUS mandatory
        DESCRIPTION
            ""
        ::= { osIdent 4 }
    
    osSwitchReference OBJECT-TYPE
        SYNTAX INTEGER ( -200..300 )
        ACCESS read-write
        STATUS mandatory
        DESCRIPTION
            ""
        ::= { osIdent 5 }
    
    osInputOpticalPowerA OBJECT-TYPE
        SYNTAX INTEGER ( -32768..32767 )
        ACCESS read-only
        STATUS mandatory
        DESCRIPTION
            ""
        ::= { osIdent 6 }
    
    osInputOpticalPowerB OBJECT-TYPE
        SYNTAX INTEGER ( -32768..32767 )
        ACCESS read-only
        STATUS mandatory
        DESCRIPTION
            ""
        ::= { osIdent 7 }
    
    
osSwitchEvent TRAP-TYPE
    ENTERPRISE nscrtvHFCemsTree
    VARIABLES { commonPhysAddress, commonNELogicalID, osCurrentWorkChannel }
    DESCRIPTION
        ""
    ::= 8686
    
    
--******************************************************************************
END
