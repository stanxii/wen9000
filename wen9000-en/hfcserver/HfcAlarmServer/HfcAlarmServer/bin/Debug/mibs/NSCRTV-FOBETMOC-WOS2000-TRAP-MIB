NSCRTV-FOBETMOC-WOS2000-TRAP-MIB DEFINITIONS ::= BEGIN

--///////////////////////////////////////////////////////////////////////////////////////////////////
--///////////////////////////////////////////////////////////////////////////////////////////////////
--///////////////////////////////////////////////////////////////////////////////////////////////////
--///////////////////////////////////////////////////////////////////////////////////////////////////
IMPORTS -- 从其它MIB导入的参数
    TRAP-TYPE
        FROM RFC-1215
    OBJECT-TYPE
        FROM RFC-1212
    NetworkAddress, IpAddress, Counter, Gauge, TimeTicks
        FROM RFC1155-SMI
    wos2kIdent
        FROM NSCRTV-FOBETMOC-ROOT
    wosHostPhysAddress, wosHostAppVersion
        FROM NSCRTV-FOBETMOC-WOS2000-MIB;

    -- 定义MAC地址类型提供该MIB文件内部使用
    PhysAddress ::= OCTET STRING (SIZE (6))

    -- 定义WOS2000的Trap通知
    wosTrapRestart TRAP-TYPE
        ENTERPRISE wos2kIdent
        VARIABLES { wosHostPhysAddress, wosHostAppVersion }
        DESCRIPTION
            ""
        ::= 1

    wosTrapDeviceUp TRAP-TYPE
        ENTERPRISE wos2kIdent
        DESCRIPTION
            ""
        ::= 2

    wosTrapDeviceDown TRAP-TYPE
        ENTERPRISE wos2kIdent
        DESCRIPTION
            ""
        ::= 3
        
--///////////////////////////////////////////////////////////////////////////////////////////////////
--///////////////////////////////////////////////////////////////////////////////////////////////////
--///////////////////////////////////////////////////////////////////////////////////////////////////
--///////////////////////////////////////////////////////////////////////////////////////////////////

END
