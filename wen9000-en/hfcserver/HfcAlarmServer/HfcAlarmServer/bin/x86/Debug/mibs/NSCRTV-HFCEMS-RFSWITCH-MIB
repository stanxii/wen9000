NSCRTV-HFCEMS-RFSWITCH-MIB DEFINITIONS ::= BEGIN

IMPORTS
    OBJECT-TYPE
        FROM RFC-1212
    DisplayString
        FROM RFC1213-MIB
    rfsIdent
        FROM NSCRTV-ROOT;

    rfsVendorOID OBJECT-TYPE
        SYNTAX OBJECT IDENTIFIER
        ACCESS read-only
        STATUS optional
        DESCRIPTION
            ""
        ::= { rfsIdent 1 }
    
    rfsRfPowerA OBJECT-TYPE
        SYNTAX INTEGER ( 0..32767 )
        ACCESS read-only
        STATUS mandatory
        DESCRIPTION
            ""
        ::= { rfsIdent 2 }

    rfsRfPowerB OBJECT-TYPE
        SYNTAX INTEGER ( 0..32767 )
        ACCESS read-only
        STATUS mandatory
        DESCRIPTION
            ""
        ::= { rfsIdent 3 }

    rfsControlMode OBJECT-TYPE
        SYNTAX INTEGER {auto(0),mannual(1)}
        ACCESS read-write
        STATUS mandatory
        DESCRIPTION
            ""
        ::= { rfsIdent 4 }

    rfsCurrentChannel OBJECT-TYPE
        SYNTAX INTEGER { channelA(0),channelB(1)}
        ACCESS read-write
        STATUS mandatory
        DESCRIPTION
            ""
        ::= { rfsIdent 5 }

    rfsChannelANumber OBJECT-TYPE
        SYNTAX INTEGER ( 0..200 )
        ACCESS read-write
        STATUS mandatory
        DESCRIPTION
            ""
        ::= { rfsIdent 6 }

    rfsChannelBNumber OBJECT-TYPE
        SYNTAX INTEGER ( 0..200 )
        ACCESS read-write
        STATUS mandatory
        DESCRIPTION
            ""
        ::= { rfsIdent 7 }

    rfsdifValue OBJECT-TYPE
        SYNTAX INTEGER ( 0..200 )
        ACCESS read-write
        STATUS mandatory
        DESCRIPTION
            ""
        ::= { rfsIdent 8 }
   
    rfsDCPowerTable OBJECT-TYPE
        SYNTAX SEQUENCE OF RfsDCPowerEntry
        ACCESS not-accessible
        STATUS mandatory
        DESCRIPTION
            ""
        ::= { rfsIdent 9 }
    
    rfsDCPowerEntry OBJECT-TYPE
        SYNTAX RfsDCPowerEntry
        ACCESS not-accessible
        STATUS mandatory
        DESCRIPTION
            ""
        INDEX { rfsDCPowerIndex }
        ::= { rfsDCPowerTable 1 }
    
    RfsDCPowerEntry ::= SEQUENCE
        {
        rfsDCPowerIndex
            INTEGER,
        rfsDCPowerVoltage
            INTEGER,
        rfsDCPowerCurrent
            INTEGER,
        rfsDCPowerName
            DisplayString
        }
    
    rfsDCPowerIndex OBJECT-TYPE
        SYNTAX INTEGER
        ACCESS read-only
        STATUS mandatory
        DESCRIPTION
            ""
        ::= { rfsDCPowerEntry 1 }
    
    rfsDCPowerVoltage OBJECT-TYPE
        SYNTAX INTEGER (-32768..32767 )
        ACCESS read-only
        STATUS mandatory
        DESCRIPTION
            ""
        ::= { rfsDCPowerEntry 2 }
    
    rfsDCPowerCurrent OBJECT-TYPE
        SYNTAX INTEGER ( 0..65535 )
        ACCESS read-only
        STATUS optional
        DESCRIPTION
            ""
        ::= { rfsDCPowerEntry 3 }
    
    rfsDCPowerName OBJECT-TYPE
        SYNTAX DisplayString
        ACCESS read-only
        STATUS mandatory
        DESCRIPTION
            ""
        ::= { rfsDCPowerEntry 4 }

END
