NSCRTV-HFCEMS-OPTICALAMPLIFIER-MIB DEFINITIONS ::= BEGIN

IMPORTS
    OBJECT-TYPE
        FROM RFC-1212
    DisplayString
        FROM RFC1213-MIB
    oaIdent
        FROM NSCRTV-ROOT;

    oaVendorOID OBJECT-TYPE
        SYNTAX OBJECT IDENTIFIER
        ACCESS read-only
        STATUS optional
        DESCRIPTION
            ""
        ::= { oaIdent 1 }
    
    oaOutputOpticalPower OBJECT-TYPE
        SYNTAX INTEGER ( 0..65535 )
        ACCESS read-write
        STATUS mandatory
        DESCRIPTION
            ""
        ::= { oaIdent 2 }
    
    oaInputOpticalPower OBJECT-TYPE
        SYNTAX INTEGER ( -128..127 )
        ACCESS read-only
        STATUS mandatory
        DESCRIPTION
            ""
        ::= { oaIdent 3 }



    oaPumpTable OBJECT-TYPE
        SYNTAX SEQUENCE OF OaPumpEntry
        ACCESS not-accessible
        STATUS mandatory
        DESCRIPTION
            ""
        ::= { oaIdent 4 }
    
    oaPumpEntry OBJECT-TYPE
        SYNTAX OaPumpEntry
        ACCESS not-accessible
        STATUS mandatory
        DESCRIPTION
            ""
        INDEX { oaPumpIndex }
        ::= { oaPumpTable 1 }
    
    OaPumpEntry ::= SEQUENCE
        {
        oaPumpIndex
            INTEGER,
        oaPumpBIAS
            INTEGER,
        oaPumpTEC
            INTEGER,
        oaPumpTemp
            INTEGER
        }
    
    oaPumpIndex OBJECT-TYPE
        SYNTAX INTEGER
        ACCESS read-only
        STATUS mandatory
        DESCRIPTION
            ""
        ::= { oaPumpEntry 1 }
    
    oaPumpBIAS OBJECT-TYPE
        SYNTAX INTEGER ( 0..65535 )
        ACCESS read-only
        STATUS mandatory
        DESCRIPTION
            ""
        ::= { oaPumpEntry 2 }
    
    oaPumpTEC OBJECT-TYPE
        SYNTAX INTEGER ( -32768..32767 )
        ACCESS read-only
        STATUS optional
        DESCRIPTION
            ""
        ::= { oaPumpEntry 3 }
    
    oaPumpTemp OBJECT-TYPE
        SYNTAX INTEGER ( 0..32768 )
        ACCESS read-only
        STATUS mandatory
        DESCRIPTION
            ""
        ::= { oaPumpEntry 4 }



    oaNumberDCPowerSupply OBJECT-TYPE
        SYNTAX INTEGER ( 0..16 )
        ACCESS read-only
        STATUS mandatory
        DESCRIPTION
            ""
        ::= { oaIdent 5 }

    oaDCPowerSupplyMode OBJECT-TYPE
        SYNTAX INTEGER { loadsharing(1), switchedRedundant(2), aloneSupply(3) }
        ACCESS read-only
        STATUS optional
        DESCRIPTION
            ""
        ::= { oaIdent 6 }
    
    oaDCPowerTable OBJECT-TYPE
        SYNTAX SEQUENCE OF OaDCPowerEntry
        ACCESS not-accessible
        STATUS mandatory
        DESCRIPTION
            ""
        ::= { oaIdent 7 }
    
    oaDCPowerEntry OBJECT-TYPE
        SYNTAX OaDCPowerEntry
        ACCESS not-accessible
        STATUS mandatory
        DESCRIPTION
            ""
        INDEX { oaDCPowerIndex }
        ::= { oaDCPowerTable 1 }
    
    OaDCPowerEntry ::= SEQUENCE
        {
        oaDCPowerIndex
            INTEGER,
        oaDCPowerVoltage
            INTEGER,
        oaDCPowerCurrent
            INTEGER,
        oaDCPowerName
            DisplayString
        }
    
    oaDCPowerIndex OBJECT-TYPE
        SYNTAX INTEGER
        ACCESS read-only
        STATUS mandatory
        DESCRIPTION
            ""
        ::= { oaDCPowerEntry 1 }
    
    oaDCPowerVoltage OBJECT-TYPE
        SYNTAX INTEGER ( -32768..32767 )
        ACCESS read-only
        STATUS mandatory
        DESCRIPTION
            ""
        ::= { oaDCPowerEntry 2 }
    
    oaDCPowerCurrent OBJECT-TYPE
        SYNTAX INTEGER ( 0..65535 )
        ACCESS read-only
        STATUS mandatory
        DESCRIPTION
            ""
        ::= { oaDCPowerEntry 3 }
    
    oaDCPowerName OBJECT-TYPE
        SYNTAX DisplayString
        ACCESS read-only
        STATUS mandatory
        DESCRIPTION
            ""
        ::= { oaDCPowerEntry 4 }

END
